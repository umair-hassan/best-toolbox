# 0 best_requirements

## #7: MEP Measurement

### #69: reaction of SI to the provided Threshold value
Each SI cell would have a 1x2 dimension, the first dimension is the SI in %MSO and the second SI is in %MT,
If the unit mode is MSO then the second coloumn remains same i.e. MSO=TH, otherwise the second dimension is updated as multiplied with the MT
This to be done on the condMat
The second element in SI pckt would be the updated SI if its %MS0 then its just exactly as same as first
otherwise its just a porportional number

### #77: Create a new MEP input panel with tabular and graphical viewer
1. complete the transfer process of data from condAll --> tabledata
2. save tabledata to condAll
3. update function if table change then viewer update callback
4. if viewer changed then table update callback
move to saving the middle pannel into obj.par such as brain state data etc
done! coffee!!!!
move onto making a condMat

#### #83: in display parameters panel add the condition's ratio to be calulated for inhibition or facilitation

#### #87: eval the timing field to get the timing vector from TableData
Have to be with square brackets necessarily
ddd=eval('[2 34]') but not ddd=eval('2 34')

#### #88: make all the INTs to STR and eval them while saving into condsAll

#### #89: when the output ir input device is added , the str on the respecite input panel is not updated actively
make a refresh callback in order to add the newly made devices , the refresh callback would jsut actually load the pars again i.e. running the same input panel function eg obj.pi_mep etc

### #78: Interaction callbacks btw Tabualr and Graphical viewer

### #79: create a condMat

### #80: create trialMat

### #81: read data from bb api

### #82: harness test

### #90: make the input dialogues of timing, si, pp, train , channel and stimulator as modal mode

### #91: when reloaded after change in table, make the Selected Child as the same condition which was updated
Simply see that which condition was updated last , may store in ab object
make the selected child equal to that

### #92: add Template Stimulation Condition Designer field
Standard Single Pulse
None
SICI (Paired Pulse)
LICI (Paired Pulse)
LICF
SICF
SAI
PAS
etc prefilled

### #93: take out the cb_BrainStateParametersPanel(~,~) and make it a methid
When the protocols are changed from the listbox, the load par is called to update the values
so in case if the BrainState is 2 i.e. Dependent then this would still just load it as if it is 1
when this will be made a methid a line will be added at the respective place in the load par function

### #94: Make a Ratio Calculator input field
that may calculat the ICF ICI

### #95: resolve the ITI conditions issue

### #96: while EditingCellData of uitable, load the right input function
Delete the tab at the start of Nconditions and make it again quickly
- Keywords: D

### #97: resolve the ITI conditions issue

### #99: BUGS

#### #101: when the Channel number is only 1 , the panel grid is not created by results panel function
Reference to non-existent field 'grid'.
Error in BEST/pr_mep (line 877)
obj.pr.clab.(obj.pr.ax_no)=uix.Panel(
'Parent', obj.pr.grid, 'Padding', 5
,'Units','normalized','Title', 'MEP
Measurement','FontWeight','bold','FontSize',12,'TitlePosition','centertop'
);
Error in BEST/resultsPanel (line 779)
obj.pr_mep;

### #100: BACKLOG

### #102: IMPROVEMENT

#### #103: Phase to be saved as a {'NaN'} in order to be saved as per other non useable parameters

### #115: Change the name of Display Channels to Target Channels
But the behaviour is good so no additional change will be required

### #117: put a marker column field on MEP and IOC condMat

## #8: Motor Hotspot Search

## #9: Motor Threshold Hunting

### #153: Log Likelihood Method
Understanding iteration:
Lets say you start with
Iteration 1: 45 , Hit
Iteration 2: 40, Hit
Iteration 3: 35, Hit
Iteration 4: 30, Miss
Iteration 5: 35, Hit
Iteration 6: 40, Miss
Iteration 7: 35, MISS (now this is important since in the iteration 5 and 3 it Hitted here , so the weights of Hits on 35 vs Miss on 35 are unbalanced - now the algorithim will first balance the weights and therefore repeat on the same intensity for a few more times: so now the Machine learning algorithim will NOT raise the intensity to 40 or so but try it as many times as it hitted previously (the event Miss is being sampled so it will be countered against hitted trials) , after all these new trials (equal to number of previously hitted trials for the same iterative condition: it will then decide either to increase or decrease depending on the situation, if the Hits are
- Rationale: function [nextInt, L] = MT_initialize_likelihood_mth()
  % Custom cdf where 'm' is mean and '0.07*m' is predifined variance
  cdfFormula = @(m) normcdf(0:0.5:100,m,0.07*m);
  % this is the cdf I am trying to emulate
  realCdf = zeros(2,201);
  spot = 1;
  for i = 0:0.5:100
  realCdf(1,spot) = i;
  spot = spot + 1;
  end
  central=40;
  first=(central*2)-20+1;
  % first=1;
  last=(central*2)+20+1;
  realCdf(2,:) = normcdf(0:0.5:100,central,0.07*central);
  %% Log likelihood function
  L = zeros(2,201);
  spot = 1;
  for i = 0:0.5:100
  L(1,spot) = i;
  spot = spot + 1;
  end
  %% Start with hit at 100% intensity and miss at 0% intensity
  spot = 1;
  for i = 0:0.5:100 % go through all possible intensities
  thisCdf = cdfFormula(i);
  % calculate log likelihood function
  L(2,spot) = log(thisCdf(last)) + log(1-thisCdf(first));
  spot = spot + 1;
  end
  %%
  %find max values
  maxValues = L(1,find(L(2,:) == max(L(2,:))));
  % Middle Value from maxValues
  nextInt = round((min(maxValues) + max(maxValues)) / 2);
  %nextInt = maxValues(round(length(maxValues)/2));
  end
  function [nextInt, L] = MT_update_likelihood_mth(MEP, L, factor)
  % Custom cdf where 'm' is mean and '0.07*m' is predifined variance
  m=1
  cdfFormula = @(m) normcdf(0:0.5:100,m,0.07*m);
  if MEP > 50
  disp('Hit')
  evokedMEP = 1;
  else
  disp('Miss')
  evokedMEP = 0;
  end
  %find max values
  maxValues = L(1,find(L(2,:) == max(L(2,:))));
  % Middle Value from maxValues
  nextInt = round((min(maxValues) + max(maxValues)) / 2);
  %nextInt = maxValues(round(length(maxValues)/2));
  % calculate updated log likelihood function
  spot = 1;
  for i = 0:0.5:100 % go through all possible intensities
  thisCdf = cdfFormula(i);
  if evokedMEP == 1 % hit!
  L(2,spot) = L(2,spot) + factor*log(thisCdf(2*nextInt+1));
  elseif evokedMEP == 0 % miss!
  L(2,spot) = L(2,spot) + factor*log(1-thisCdf(2*nextInt+1));
  end
  spot = spot + 1;
  end
  %find max values
  maxValues = L(1,find(L(2,:) == max(L(2,:))));
  % Middle Value from maxValues
  nextInt = round((min(maxValues) + max(maxValues)) / 2);
  %nextInt = maxValues(round(length(maxValues)/2));
  display(sprintf('using next intensity: %.2f', nextInt))
  end
  function [nextInt, L] = MT_initialize_likelihood_psychmth()
  % Custom cdf where 'm' is mean and '0.07*m' is predifined variance
  cdfFormula = @(m) normcdf(0:0.1:10,m,0.07*m);
  % this is the cdf I am trying to emulate
  realCdf = zeros(2,101);
  spot = 1;
  for i = 0:0.1:10
  realCdf(1,spot) = i;
  spot = spot + 1;
  end
  central=3;
  first=(central*10+1)-10;
  last=(central*10+1)+10;
  realCdf(2,:) = normcdf(0:0.1:10,central,0.07*central);
  %% Log likelihood function
  L = zeros(2,101);
  spot = 1;
  for i = 0:0.1:10
  L(1,spot) = i;
  spot = spot + 1;
  end
  %% Start with hit at 100% intensity and miss at 0% intensity
  spot = 1;
  for i = 0:0.1:10 % go through all possible intensities
  thisCdf = cdfFormula(i);
  % calculate log likelihood function
  L(2,spot) = log(thisCdf(last)) + log(1-thisCdf(first));
  spot = spot + 1;
  end
  %%
  %find max values, returns intensity (no indice problem)
  maxValues = L(1,find(L(2,:) == max(L(2,:))));
  % Middle Value from maxValues
  nextInt = round((min(maxValues) + max(maxValues))/2,1);
  % nextInt=sprintf('%.1f', nextInt)
  end
  function [nextInt, L] = MT_update_likelihood_psychmth(MEP, L, factor)
  % Custom cdf where 'm' is mean and '0.07*m' is predifined variance
  cdfFormula = @(m) normcdf(0:0.1:10,m,0.07*m);
  if MEP > 50
  disp('Hit')
  evokedMEP = 1;
  else
  disp('Miss')
  evokedMEP = 0;
  end
  %find max values
  maxValues = L(1,find(L(2,:) == max(L(2,:))));
  % Middle Value from maxValues
  nextInt = round((min(maxValues) + max(maxValues))/2,1);
  if nextInt==0.1
  nextInt=0.4;
  end
  if nextInt==10
  nextInt=9;
  end
  % nextInt=sprintf('%.1f', maxValues)
  %nextInt = maxValues(round(length(maxValues)/2));
  % calculate updated log likelihood function
  spot = 1;
  for i = 0:0.1:10 % go through all possible intensities
  thisCdf = cdfFormula(i);
  central=nextInt*10+1;
  if evokedMEP == 1 % hit!
  L(2,spot) = L(2,spot) + factor*log(thisCdf(central));
  elseif evokedMEP == 0 % miss!
  L(2,spot) = L(2,spot) + factor*log(1-thisCdf(central));
  end
  spot = spot + 1;
  end
  %find max values
  maxValues = L(1,find(L(2,:) == max(L(2,:))));
  maxValues
  % Middle Value from maxValues
  nextInt = round((min(maxValues) + max(maxValues))/2,1);
  % nextInt=sprintf('%.1f', maxValues);
  %nextInt = maxValues(round(length(maxValues)/2));
  display(sprintf('using next intensity: %.2f', nextInt))
  end

## #10: MEP IOC

### #66: Adding feature to choose sp/pp capability

#### #68: prepare condMat and trialMat

### #150: IOC simple pchip based code
x = [30 40 45 50 60 70 80 90 95 96];
y = [40 44 46 52 300 700 900 910 915 910 ] %3 3.2 2.9 5 8 9 10 10.1 10.12]+46;
for i=1:numel(y)-1
i
m(i)=(y(i+1)-y(i))/(x(i+1)-x(i));
m
end
[sortedX ,sortedidx]= sort(m(:),'descend');
ipx=mean(x(sortedidx(1):sortedidx(1)+1))
ipy=mean(y(sortedidx(1):sortedidx(1)+1))
mtop3=max(sortedX)
mMean=mean(mtop3)
xq1 = 30:.0001:95;
p = pchip(x,y,xq1);
plot(x,y,'o',xq1,p,'-')
hold on
plot(ipx,ipy,'*')
[value_pt , index_pt] = min(abs(p-(0.993*(max(p)) ) ) ); %99.3 % of MEP max %TODO: Test it with longer plateu
pt_x=xq1(index_pt);
pt_y=p(index_pt);
hold on
plot(pt_x,pt_y,'*')
[value_th , index_th] = min(abs(p-50 ) ); % change the 50 to be adaptive to what threshold in mV or microV is given
thx=xq1(index_th);
hold on
plot(thx,50,'*')

## #11: EEGTMS

## #12: rTMS Intervention
https://www.ncbi.nlm.nih.gov/pmc/articles/PMC3260536/

## #14: TEP Hotspot Search

## #15: TEP Measurement

## #16: TEP IOC

## #20: Multimodal Experiment

### #22: Interactive application

#### #23: Iconing of library
List of icons:
stimulator (any device icon would work here)
condition (any panel with tabs would here )
sp (sq wave)
pp cs+ts
train (three sq waves)
Icons for later on:
Audio Masking
Audio Stimulus + Video stimulus would go as part in the hardware configuration panel
-------------------------------------------------------------------------------------
Fix the icon sizes, put them in one row (small ones) and make their padding on both sides as responvie
put fixed icon image sizes over them
sp, pp, train, stimulator spark, +,
all these buttons to go there
Implementation view:
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
##### #65: Beautification, aspect ratio of the hegiths and widths in the first input panel

#### #29: interacting with axes to add pulses on any stimulator
add ui menu to each of the pulses
uimenu will check how many stimulators are available in that condition
uimenu will show those stimulator 1 ..... stimulator N on the menu to select for
user will select any one
the pulse would go there
OR
click on the pulse buttons
a easy to use selectionox to be open up infront of screen to choose on which axes it has to be placed
as soon as the user clicks on the stim no, close that dialogue box and place the pulse immediately
just take the stim no flag using this approach
OR
select the pulse
left click on that very stimulator's line plot where you want to place it, and it would just place it there
(just that the lines needs to be slightly thick)
Finally this idea is great
click on the plot
use the button down function to chane its colour to red (which means it is selected now)
also assign the slcted no of stimulator to the rspctv var
then click on the pulse icon
and the pulse would be added to that very stimulator
also change its colour back to the black as soon as the pulse is added!
Later on:
drag and drop interaction can be placed but thats so much time consuiming therefore not in the list even yet

#### #30: deleting a particularly added pulse
method:
click on the dialogue box opener (which is used to specify the parameters of pulse)
click on the delete button over inside that button, just besides OK button
give a callback to that button
callback:
decrease pulse count for that stimulator by 1 (pulse_count-1)
delete the timing of that very exact pulse from the stim_timing vector for that very stimulator

#### #31: deleting a particular added stimulator
method:
click on the dialogue box opener (which is used to specify the device_name listbox of the )
click on the delete button over inside that button, just besides OK button
give a callback to that button
callback:
decrease pulse count for that stimulator by 1 (pulse_count-1)
delete the timing of that very exact pulse from the stim_timing vector for that very stimulator

#### #32: changing the Target chanel using the Global Channel Selector
The global channel selector pannel would save the data in a cell str format to the targetChannel string

#### #33: callback based saving of the inputs data
Display periods are still not linked properly

#### #34: callback based reloading of the axes when measures are changed from listbox
obj.pi.mm.cond.no= read the condition numbers from the file
for loop on obj.cb_pi_mm_conditions to make all the conds
update the cond.no field as per the index of the foor loop
update obj.pi.mm.stim.(cd).no for all the stimulators on this cond
function cb_pi_mm_stim(obj)
apply for loop to produce all the stimulator plots
apply for loop to procue all the pulses on each stimulator plot

##### #49: default par multimodal
obj.bst.inputs.ylimMax=2000;
obj.bst.inputs.ylimMin=-2000;
obj.bst.inputs.mep_onset=(obj.pi.mm.mepOnset.String)/1000;
obj.bst.inputs.mep_offset=(obj.pi.mm.mepOffset.String)/1000;
obj.bst.inputs.stim_mode='MSO'
obj.bst.inputs.stop_event=0
thse kind of parameters have to be dealt with yet

##### #62: resolve the issue of displayChannel default par and load par

#### #41: warning and error handling at the frontend interface
eg if someone tries to add different kind of pulses on one stimulators

##### #50: if no stimulator is selected but pulse is selected, throw an error dialogue box

##### #51: if different kind of pulses are being placed on a stimulator, throw an error dialogue box
before adding the pulse,
in the start of the pulse callback
check if the previous pulses exists on the same stimulator
if yes, check if this stim_mode is same as of that pulse
otherwise throw an error

##### #61: if more than one values being added as SI, CS, TS, ISI or Th value , time vector , throws an error

#### #44: create the pulse shapes interactively as per the given inputs

##### #45: on the target channel axes line the left tick mark is visible therefore switch the tickmarks

#### #63: duplicae to make a new identical condition with new cond No
to duplicate a particular condition
click on that condition tab (means open that condition 0r make it active)
click on the gray area (i.e. the panel area)
a context menu will open up allowing you to either delete or duplicate the condition
Pseudo code
check for total no of conds already available using condAll numering
check which is the current condition
assign a new copy
load the condition pi function once again

#### #64: delete a condition and remove it from pars

### #24: MEP Measurement

### #25: IOC Measurement

#### #72: add a row asking about IOC to plot between what 2 pars out of total of 3 pars, ISI, CS, TS

##### #73: create an error handle for this in case if any imbalncing is occuring
check if all the factors are balanced i.e. all the conditions wshould be comprable and should have only 1 varying variable e.g. ISI, or CS or TS
and that varying effect should respectively project onto all conditions matlab vo sab ki values tabdel hon beshak but parameters same ahy
agr ISI change ho rha he across condition to sirf vohi ho otherwise ERROR throw ker do
STATS k software me bhi yehi hota he

### #26: Motor Thresholding

### #27: Psychometric Thresholding

### #28: EEGTMS

### #54: EEG TMS MEP Measurement

### #55: EEGTMS MEP IOC

## #35: BEST GUI

### #37: Cleaning
No command should be visible at the command line except for those coming from external toolboxes e.g. fieldtrip magic or anything ekse

#### #46: Nothing to be printed on command line

#### #48: variables naming convention check
read this: https://www.ee.columbia.edu/~marios/matlab/MatlabStyle1p5.pdf

## #38: Hardware Configuration

### #39: Auditory stimulus device addition among output devices

### #40: Visual stimulus device addition among output devices

## #52: EEGTMS MEP Measurement

## #53: EEGTMS MEP IOC

## #56: rsEEG Analysis

## #57: ERP Analysis

## #58: BOSS Device API

### #104: read neurone protocol file and save the data of ch labels in that hardware device package
- Rationale: function cb_add_NeurOneProtocolFile(~,~)
  [file,path] = uigetfile('*.xml');
  if (file~=0)
  fullfilepath=[path file];
  clab = neurone_digitalout_clab_from_xml(xmlread(fullfilepath));
  obj.hw.vbox_rp.NeurOneProtocolChannelLabels=clab; %1xn CellString
  obj.hw.vbox_rp.prtcl_name.String=file;
  else
  errordlg('No Protocol is attached. Attach the Protocol again to add a NeurOne device','BEST Toolbox');
  end
  function digitalout_clab = neurone_digitalout_clab_from_xml(protocolXmlDoc)
  % protocolXmlDoc - exported NeurOne XML protocol (used to extract digital out channels)
  % Example: neurone_digitalout_clab_from_xml(xmlread('FRONTHETA v2.xml'))
  % parse the NeurOne protocol in order to determine the realtime out channels
  inputIdNameMap = containers.Map;
  allInputElements = protocolXmlDoc.getElementsByTagName('DataSetProtocol').item(0).getElementsByTagName('TableProtocolInput');
  for k = 0:allInputElements.getLength-1
  thisElement = allInputElements.item(k);
  inputName = thisElement.getElementsByTagName('Name').item(0).getFirstChild.getData;
  %inputNumber = thisElement.getElementsByTagName('InputNumber').item(0).getFirstChild.getData;
  inputId = thisElement.getElementsByTagName('Id').item(0).getFirstChild.getData;
  inputIdNameMap(char(inputId)) = inputName;
  end
  outputChannelNumberNameMap = containers.Map;
  allOutputElements = protocolXmlDoc.getElementsByTagName('DataSetProtocol').item(0).getElementsByTagName('TableOutputActive');
  for k = 0:allOutputElements.getLength-1
  thisElement = allOutputElements.item(k);
  outputChannelNumber = thisElement.getElementsByTagName('OutputChannelNumber').item(0).getFirstChild.getData;
  inputId = thisElement.getElementsByTagName('InputId').item(0).getFirstChild.getData;
  inputName = inputIdNameMap(char(inputId));
  outputChannelNumberNameMap(char(outputChannelNumber)) = inputName;
  end
  sortedOutputChannels = sort(cellfun(@str2num, outputChannelNumberNameMap.keys));
  digitalout_clab = [{}];
  i = 0;
  for channel = sortedOutputChannels
  i = i + 1;
  digitalout_clab(i) = outputChannelNumberNameMap(num2str(channel));
  end
  end
  end

#### #109: add 2 fields about EEG and AUX channel numbers as well
Try to get this automatically from the xml
function hw_input_neurone(obj)

### #105: load defaults of boss device to the initialzation function
obj.bb.calibration_mode = 'no';
obj.bb.armed = 'no';
obj.bb.sample_and_hold_period=0;
obj.bb.theta.ignore, pause(0.1)
obj.bb.beta.ignore, pause(0.1)
obj.bb.alpha.ignore, pause(0.1)

### #106: load channel labels to spatial filter
clab{65} = 'FCz';
obj.bb.spatial_filter_clab = clab;

### #107: set spatial filter channels and set weight
% set a spatial filter to C3 hjorth
set_spatial_filter(obj.bb, {'C3', 'FC1', 'FC5', 'CP1', 'CP5'}, [1 -0.25 -0.25 -0.25 -0.25], 1)
set_spatial_filter(obj.bb, {}, [], 2)

### #110: load defaults of MontageChannels and Montage Weights

### #111: read IP and IEEG and plot them as per the condition

## #59: FieldTrip Real-Time Buffer API

## #60: Spike2/Signal Integeration

## #70: General Features

### #71: make a unit's vector corrosponding to condMat (also same exactl mat would be the unit Matrix for trialMat)
the units_condMat,
would contain a 1xN cell array descibing units of all the elements of condMat or trialMat

### #74: saving of protocol and load the protocol

### #75: locking down paramaters so that they are not accidently changed

### #112: Baseline correction
https://www.mathworks.com/matlabcentral/answers/340037-baseline-correction-using-media-filter

### #113: Basic line noise correction
https://www.mathworks.com/help/signal/ug/remove-the-60-hz-hum-from-a-signal.html
% Fs = 5000; % Sampling Frequency (Hz)
% Fn = Fs/2; % Nyquist Frequency (Hz)
% Wp = [1.0 100]/Fn; % Passband Frequencies (Normalised)
% Ws = [0.5 101]/Fn; % Stopband Frequencies (Normalised)
% Rp = 1; % Passband Ripple (dB)
% Rs = 2; % Stopband Ripple (dB)
% [n,Ws] = cheb2ord(Wp,Ws,Rp,Rs); % Filter Order
% [z,p,k] = cheby2(n,Rs,Ws); % Filter Design
% [sosbp,gbp] = zp2sos(z,p,k); % Convert To Second-Order-Section For Stabilityd = designfilt('bandstopiir','FilterOrder',2, ...
'HalfPowerFrequency1',49,'HalfPowerFrequency2',51, ...
'DesignMethod','butter','SampleRate',5000);for i=1:238
% dt = filtfilt(sosbp, gbp, data(i,:));
dt(i,:) = filtfilt(d, raw_data(i,:));
% dt = filtfilt(sosbp, gbp, dt);enddata=dt;
i=0;
while i<238
i=i+1;
m=mean(data(i,100:120));
m=abs(m);
if(m>0)
data(i,:)=data(i,:)+m;
end
if(m<=0)
%
data(i,:)=data(i,:)-m;
end
end
i=0;
while i<238
i=i+1;
m=mean(data(i,100:120));
m=abs(m);
if(m>0)
data(i,:)=data(i,:)-m;
end
if(m<=0)
%
c(i,:)=data(i,:)+m;
end
end
figure (1)
hold on;
for i=1:238
plot(data(i,:),'color',[0.35 0.35 0.35]);
if(i==238)
plot(data(i,:),'color','r');
hold on;
plot(mean(data),'color','k');
endend

### #114: Line Noise Correction
See the sample algorithim in the rationale

### #118: make the data cleaning

### #143: Flexible
BS2
Minimum ITI
Condition No
Phase
Amp Low
Amp High
BS1
ITI
Condtion No

### #144: Pych toolbox interaction

## #76

## #84: Making Axes new window
https://www.mathworks.com/matlabcentral/answers/157355-grouping-figures-separately-into-windows-and-tabs
https://www.mathworks.com/matlabcentral/answers/162407-global-position-of-docked-figures-window
- Rationale: desktop = com.mathworks.mde.desk.MLDesktop.getInstance;
  myGroup = desktop.addGroup('myGroup');
  desktop.setGroupDocked('myGroup', 0);
  myDim = java.awt.Dimension(4, 2); % 4 columns, 2 rows
  % 1: Maximized, 2: Tiled, 3: Floating
  desktop.setDocumentArrangement('myGroup', 2, myDim)
  figH = gobjects(1, 8);
  bakWarn = warning('off','MATLAB:HandleGraphics:ObsoletedProperty:JavaFrame');
  for iFig = 1:8
  figH(iFig) = figure('WindowStyle', 'docked', ...
  'Name', sprintf('Figure %d', iFig), 'NumberTitle', 'off','NumberTitle', 'off','ToolBar','none','MenuBar','none','visible','off');
  drawnow;
  pause(0.02); % Magic, reduces rendering errors
  set(get(handle(figH(iFig)), 'javaframe'), 'GroupName', 'myGroup');
  plot(1:10, rand(1, 10));
  end
  warning(bakWarn);
  for iFig = 1:8
  set( figH(iFig),'visible','on')
  end
  save axes instead of figure
  save using the file name and target variable name properly this may cause the issue of serialization that wasted my enough time

## #85

## #86

## #98

## #116

## #119: Today
Start making the hotspot panel
make the condMat + add another field of channel labels for pr so that they can be shown on the Title of Panel
run on the automated mode
save the data
reload the data
reload the results
add fieldtrip
all possible error handles
vehaviour of the 3 big panels i.e. Designer , Input Panel and Results , make the designer as of fixed width

### #125: show the channel name/condition specification (decide first) on the title of that ax

### #128: make the hotspot input panel COMPLETE!

### #129: Save the data
Inside Par:
All information as it is
Inside Data:
TrialMatrix
TrialMatrixLabels
ConditionMatrix
ConditionMatrixLabels
RawData
Results
Figures

### #130: Load the protocol and data

### #131: Load the results from ax
f1 = figure % Open a new figure with handle f1
s = copyobj(h,f1) % Copy axes object h into figure f1

### #132: FieldTrip cycle

### #133: All error handles
out of bound channels
out of bound ITI
out of bound everything associated to input fields

### #134: saving figures in the CD and turning this option off

### #135: pause/resume/stop callbacks

### #136: uimenu feature of export as matlab figure (make a new figure and copy the axes for that image)

### #137: toolbox settings options
AutoSave on or off
Results Figure Saving on or off

### #139: Open Close Hardware Config

### #140: Add a status to listbox: completed on 21.2.2020 time etc

### #141: Run/Stop, Pause/Unpause buttons unders listbx

## #127: Done

### #126: IF Possible show the legend
https://public.brain.mpg.de/Laurent/SheinIdelsonetal2017/NSKToolbox/timeSeriesViewer/GUILayout/layoutdoc/User%20guide2_3.html

## #142: Enable off uicontrol, table, graphical for the multimodal methods

## #145: Session Loading dynamic time wait
If all the data from the mat file does not get stored in the new object then wait untill that is achieved becaue otherwise it will create an error;

## #146: Toolbox Settings Panel
Give option to choose from the randomizer
https://www.mathworks.com/help/matlab/ref/rng.html
rng('default')
or allow them to define their own randomizer

## #147

## #148: MEP Plot Color Orders
https://www.rapidtables.com/web/color/RGB_Color.html

## #149

## #151: Tests

### #152: IOC
This test was yielded when the Response Function 2 3 4 5 6/1
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
## #154: Reference Documents
https://tsgdoc.socsci.ru.nl/images/a/ac/Magpro_family.pdf
